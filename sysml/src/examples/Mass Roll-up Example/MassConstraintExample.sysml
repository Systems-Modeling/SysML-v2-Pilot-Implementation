package MassConstraintExample {
	import ISQ::*;
	import SI::*;
	import ScalarFunctions::*;
	
	part def Engine {
		attribute m :> mass;
	}
	
	part def Transmission {
		attribute m :> mass;
	}
	
	part def Vehicle1 {
		attribute m : MassValue = eng::m + trans::m;
		
		part eng : Engine {
			attribute :>> m : MassValue;
		}
		
		part trans : Transmission {
			attribute :>> m : MassValue;
		}
	}
	
	part def Vehicle2 {
		assert constraint { m == eng::m + trans::m }
		
		attribute m : MassValue;
		
		part eng : Engine {
			attribute :>> m : MassValue;
		}
		
		part trans : Transmission {
			attribute :>> m : MassValue;
		}
	}
	
	constraint def MassConstraint3 (
		totalMass : MassValue, 
		partMasses : MassValue[0..*]) {
			
		totalMass == sum(partMasses)
	}
	
	part def Vehicle3 {
		assert constraint massConstraint : MassConstraint3 (
			totalMass = m, 
			partMasses = (eng::m, trans::m)
		);
		
		attribute m : MassValue;
		
		part eng {
			attribute m : MassValue;
		}
		
		part trans {
			attribute m : MassValue;
		}
	}
	
	constraint def MassConstraint4 (
		totalMass : MassValue, 
		partMasses : MassValue[0..*]);
	
	constraint mc : MassConstraint4 (
		totalMass : MassValue, 
		partMasses : MassValue[0..*]) {
		
		totalMass == sum(partMasses)
	}
	
	part def Vehicle4 {
		assert mc (
			totalMass = m, 
			partMasses = (eng::m, trans::m)
		);
		
		attribute m : MassValue;
		
		part eng : Engine {
			attribute :>> m : MassValue;
		}
		
		part trans : Transmission {
			attribute :>> m : MassValue;
		}
	}
	
	constraint def MassLimit (
		mass : MassValue, 
		maxMass : MassValue) {
			
		mass <= maxMass
	}
	
	part def Vehicle5 {
		assert constraint ml : MassLimit (
			mass = m, 
			maxMass = 2500@[kg]
		);
		
		attribute m : MassValue = eng::m + trans::m;
		
		part eng : Engine {
			attribute :>> m : MassValue;
		}
		
		part trans : Transmission {
			attribute :>> m : MassValue;
		}
	}	
	
}
