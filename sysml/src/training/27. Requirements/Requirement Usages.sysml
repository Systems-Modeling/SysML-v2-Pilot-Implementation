package 'Requirement Usages' {
	import SI::*;
	import 'Requirement Definitions'::*;
	
	requirement id '1.1' fullVehicleMassLimit : VehicleMassLimitationRequirement {
		attribute :>> massReqd = 2000@[kg];
		
		assume constraint {
			doc /* Full tank is full. */
			vehicle::fuelMass == vehicle::fuelFullMass
		}
	}
	
	requirement id '1.2' emptyVehicleMassLimit : VehicleMassLimitationRequirement {
		attribute :>> massReqd = 1500@[kg];
		
		assume constraint {
			doc /* Full tank is empty. */
			vehicle::fuelMass == 0@[kg]
		}
	}
	
}
