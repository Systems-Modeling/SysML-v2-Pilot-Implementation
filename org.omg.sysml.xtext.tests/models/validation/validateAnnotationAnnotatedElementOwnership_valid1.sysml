// Constraint: validateAnnotationAnnotatedElementOwnership (context: Annotation)
// An Annotation owns its annotatingElement if and only if it is owned by its annotatedElement.
// (owningAnnotatedElement <> null) = (ownedAnnotatingElement <> null)
package validateAnnotationAnnotatedElementOwnership_valid1 {
	part p {
		comment about p /* */
	}
}
