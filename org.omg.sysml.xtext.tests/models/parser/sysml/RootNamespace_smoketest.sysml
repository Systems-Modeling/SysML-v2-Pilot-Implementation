public#MyType#MyType package<'Unrestricted Name'>BasicName{
	alias<BasicName>BasicName for MyElement{
		comment about MyElement,MyElement,MyElement locale"Sample string"/* Sample comment *//* Sample comment */
	}
	private import all MyMembership::**{
	}
}
filter if null??null?null|null else null;
state def{
	action ordered;
	accept at null if null do then MyFeature;
}
state def{
	action ordered;
	if null do then MyFeature;
}
state def{
	action ordered;
	accept at null then MyFeature;
}
assert not satisfy MyFeature nonunique ordered:MyType:MyType{
}
comment about MyElement/* Sample comment */assert not satisfy requirement ordered=null;
state def{
	action ordered;
	transition then MyFeature;
}
@:MyType about MyElement{
	:>>MyFeature{
		alias for MyElement;
		alias for MyElement;
	}
	MyFeature;
}
state def{
	action ordered;
	if null then MyFeature;
}
state def{
	transition MyFeature.MyFeature then MyFeature;
}
action def{
	send null to null;
}
ordered default=null;
filter MyElement meta MyType;
include MyFeature ordered{
}
assert MyFeature ordered;
action def{
	send null;
}
filter null->MyFeature.MyFeature.MyFeature MyType;
#MyType@MyType{
	ref MyFeature ordered=null{
		protected import MyNamespace::*::**;
		public import MyMembership;
	}
}
#MyType@MyType{
	redefines MyFeature{
	}
}
filter as MyType;
exhibit MyFeature{
}
exhibit state ordered=null;
include MyFeature;
action def{
	loop{
	}
}
action def{
	first MyFeature.MyFeature if null then MyFeature;
}
filter null->MyFeature.MyFeature(null,null,null);
comment/* Sample comment */event occurrence ordered;
assert constraint ordered;
action def{
	loop action ordered{
	}
}
abstract individual def;
ordered default null;
event occurrence;
connect(MyFeature,MyFeature);
interface ordered connect(MyFeature,MyFeature);
viewpoint def{
	assume constraint ordered;
}
viewpoint def{
	frame concern ordered;
}
viewpoint def{
	verify#MyType#MyType ordered;
}
viewpoint def{
	verify requirement ordered;
}
standard library package;
metadata MyType;
view def{
	render#MyType#MyType;
}
view def{
	render rendering;
}
state def{
	action ordered;
	then MyFeature;
}
state def{
	action ordered;
	transition do MyFeature{
	}
	then MyFeature;
}
state def{
	action ordered;
	transition do accept at null{
	}
	then MyFeature;
}
state def{
	action ordered;
	transition do send null{
	}
	then MyFeature;
}
state def{
	action ordered;
	transition do assign MyFeature.MyFeature:=null{
	}
	then MyFeature;
}
viewpoint def{
	verify MyFeature:MyType:MyType;
}
action def{
	if null{
	}
}
language"Sample string"/* Sample comment */filter.55;
filter 55E55;
ordered:=null;
view def{
	render MyFeature ordered;
}
state def{
	do accept after null;
}
viewpoint def{
	assume MyFeature ordered;
}
viewpoint def{
	frame MyFeature ordered;
}
message MyFeature to MyFeature;
message ordered=null;
succession flow ordered=null;
action def{
	action terminate;
}
variation#MyType def;
calc ordered;
doc/* Sample comment */binding[true]ordered:MyType bind MyFeature=MyFeature;
ordered=null;
public import MyNamespace::*[null];
view def{
	render MyFeature;
}
view{
	expose MyNamespace::*;
}
interface ordered=null;
succession flow ordered of[true]MyType;
state def{
	do accept when null;
}
viewpoint def{
	assume MyFeature;
}
viewpoint def{
	frame MyFeature;
}
viewpoint def{
	verify MyFeature;
}
action def{
	send;
}
enum def{
	enum;
	;
}
state def{
}
metadata def;
/* Sample comment */public import MyMembership[null][null];
public import MyNamespace::*::**[null];
interface def{
	variant MyFeature;
}
bind MyFeature=MyFeature;
interface ordered connect(MyFeature,MyFeature,MyFeature);
succession flow ordered of[true]:MyType:MyType;
succession flow ordered of MyType;
viewpoint def{
	require#MyType#MyType ordered;
}
viewpoint def{
	frame#MyType#MyType ordered;
}
allocation ordered;
succession flow ordered from MyFeature.MyFeature to MyFeature;
action def{
	send;
	if null then MyFeature;
}
action def{
	send;
	else MyFeature;
}
action def{
	loop{
	}
}
constraint def{
	return ordered;
}
dependency MyElement to MyElement;
verification def specializes MyClassifier;
enum def{
}
view def{
}
package;
verification def{
	subject;
}
verification def{
	actor;
}
viewpoint def{
	stakeholder;
}
verification def{
	objective ordered;
}
allocate MyFeature to MyFeature;
succession flow ordered from MyFeature to MyFeature;
filter null->MyFeature.MyFeature(null);
filter null->MyFeature.MyFeature(MyFeature=null);
binding ordered:MyType bind MyFeature=MyFeature;
binding ordered:>MyFeature bind MyFeature=MyFeature;
binding ordered=>MyFeature bind MyFeature=MyFeature;
binding ordered:>>MyFeature bind MyFeature=MyFeature;
constraint def{
}
state def{
	public import MyMembership;
}
state def{
	alias for MyElement;
}
state def{
	package;
}
state def{
	variant MyFeature:MyType:MyType;
}
state def{
	end ref;
}
attribute def{
	alias for MyElement;
}
attribute def{
	public import MyMembership;
}
binding BasicName bind MyFeature=MyFeature;
view{
	expose MyMembership;
}
interface def{
	package;
}
interface def{
	ref;
}
interface def{
	alias for MyElement;
}
interface def{
	public import MyMembership;
}
state def{
	transition<BasicName>BasicName:MyType,MyFeature.MyFeature,~MyConjugatedPortDefinition references MyFeature:>MyFeature,MyFeature.MyFeature,MyFeature=>MyFeature.MyFeature first MyElement accept:>>MyFeature,MyFeature.MyFeature,MyFeature:MyType:MyType:MyType at all MyType via null istype MyType if+null do then[true]BasicName::>MyFeature.MyFeature.MyFeature{
		then[MyElement..true]in derived abstract constant ref individual snapshot#MyType#MyType action<BasicName>default:=MyElement@@MyType{
		}
		then MyFeature{
			then variation occurrence:MyType[true]ordered nonunique=null;
			occurrence;
		}
		then MyFeature;
		first MyElement;
		then MyFeature;
		then MyFeature;
	}
}
state def{
	do action ordered=null;
}
state def{
	exit accept at null;
}
state def{
	action ordered;
	transition do action ordered then MyFeature;
}
state def{
	action ordered;
	transition do accept at null then MyFeature;
}
state def{
	action ordered;
	transition do send null then MyFeature;
}
state def{
	action ordered;
	transition do assign MyFeature.MyFeature:=null then MyFeature;
}
viewpoint def{
	frame#MyType#MyType concern ordered;
}
viewpoint def{
	verify#MyType#MyType requirement ordered;
}
viewpoint def{
	actor;
}
viewpoint def{
	stakeholder#MyType#MyType;
}
verification def{
	objective#MyType#MyType ordered;
}
enum def{
	;
}
rep language"Sample string"/* Sample comment */#MyType#MyType dependency from MyElement,MyElement,MyElement to MyElement,MyElement,MyElement;
abstract attribute def;
#MyType#MyType enum def{
	doc locale"Sample string"/* Sample comment *//* Sample comment */
}
occurrence def;
individual#MyType#MyType def:>MyClassifier,MyClassifier,MyClassifier{
}
item def;
part def;
connection def;
flow def;
abstract interface def{
	then end;
	end;
}
allocation def;
#MyType#MyType port def;
action def;
calc def;
state def parallel{
	action ordered;
	entry;
}
constraint def;
requirement def;
concern def;
case def;
analysis def;
verification def;
individual#MyType#MyType use case def;
view def{
	filter null;
	render rendering;
}
viewpoint def;
rendering def;
abstract#MyType#MyType metadata def;
#MyType#MyType def;
#MyType#MyType@defined by MyType about MyElement,MyElement,MyElement{
	standard library#MyType#MyType package{
	}
	package;
}
binding ordered defined by MyType,MyType bind MyFeature=MyFeature;
binding ordered subsets MyFeature,MyFeature bind MyFeature=MyFeature;
binding ordered crosses MyFeature bind MyFeature=MyFeature;
binding ordered redefines MyFeature,MyFeature bind MyFeature=MyFeature;
filter 55;
filter 55.55e+55;
filter*;
filter false;
filter 55e-55;
filter null or null;
filter null and null;
filter null implies null;
filter null&null;
filter null xor null;
filter null..null;
filter null==null;
filter null!=null;
filter null===null;
filter null!==null;
filter null<null;
filter null>null;
filter null<=null;
filter null>=null;
filter null+null;
filter null-null;
filter null*null;
filter null/null;
filter null%null;
filter null^null;
filter null**null;
filter-null;
filter~null;
filter not null;
filter null hastype MyType;
filter null@MyType;
filter null.?;
;
filter null.;
;
filter null->MyElement;
;
filter();
filter(null,null);
interface def{
	variant ref;
}
interface def{
	variant attribute;
}
interface def{
	variant end ordered#MyType#MyType binding ordered bind MyFeature=MyFeature;
}
interface def{
	variant succession ordered first MyFeature then MyFeature;
}
interface def{
	variant occurrence;
}
interface def{
	variant individual;
}
interface def{
	variant individual snapshot#MyType#MyType;
}
interface def{
	variant event MyFeature ordered;
}
interface def{
	variant item;
}
interface def{
	variant part;
}
interface def{
	variant view ordered=null{
		filter null;
		render#MyType#MyType rendering;
	}
}
interface def{
	variant rendering;
}
interface def{
	variant port;
}
interface def{
	variant connection ordered connect MyFeature to MyFeature;
}
interface def{
	variant interface ordered connect MyFeature to MyFeature{
	}
}
interface def{
	variant allocation ordered allocate(MyFeature,MyFeature,MyFeature,MyFeature);
}
interface def{
	variant message ordered of MyType[true]from MyFeature to MyFeature;
}
interface def{
	variant flow MyFeature to MyFeature;
}
interface def{
	variant succession flow ordered of[true]MyType from MyFeature.MyFeature.MyFeature.MyFeature to MyFeature;
}
interface def{
	variant state ordered;
}
attribute;
enum;
bind MyFeature=MyFeature;
first MyFeature then MyFeature;
#MyType#MyType;
out ref;
inout ref;
event MyFeature;
item;
part;
view{
}
rendering;
port;
connection ordered=null;
flow ordered;
view;
view{
	package;
}
interface([true]BasicName::>MyFeature,MyFeature,MyFeature,MyFeature);
interface def;
interface def{
	attribute;
}
interface def{
	enum;
}
interface def{
	bind MyFeature=MyFeature;
}
interface def{
	first MyFeature then MyFeature;
}
interface def{
	then snapshot;
}
interface def{
	then constraint ordered;
}
requirement ordered;
concern ordered;
case ordered;
analysis ordered;
verification ordered;
use case ordered;
viewpoint ordered;
perform action ordered;
exhibit MyFeature nonunique parallel{
	then action ordered;
	transition accept at null if null do then MyFeature;
	then MyFeature;
	entry;
	then MyFeature;
	if null then MyFeature;
}
include use case ordered=null{
	subject;
	actor#MyType#MyType;
	null
}
assert not MyFeature;
assert not satisfy MyFeature by MyFeature.MyFeature{
	subject#MyType#MyType;
	assume#MyType#MyType constraint ordered=null{
		return ordered;
		individual timeslice#MyType#MyType merge ordered;
		null#(null)[null,].MyElement
	}
}
state def{
	occurrence;
}
state def{
	do accept:MyType ordered=null;
}
state def{
	action ordered;
	transition do MyFeature ordered{
		then individual#MyType#MyType;
		package;
	}
	then MyFeature;
}
state def{
	action ordered;
	transition do action accept at null{
		package;
		package;
	}
	then MyFeature;
}
state def{
	action ordered;
	transition do action send null via null{
		package;
		package;
	}
	then MyFeature;
}
state def{
	action ordered;
	transition do action assign(null).MyFeature.MyFeature:=null{
		package;
		package;
	}
	then MyFeature;
}
state def{
	do send null;
}
state def{
	do assign MyFeature.MyFeature:=null;
}
viewpoint def{
	variant ref;
}
verification def{
	package;
}
action def{
	action send via null to null;
}
action def{
	accept at null;
}
action def{
	assign MyFeature.MyFeature:=null;
}
action def{
	terminate null;
}
action def{
	if null{
	}
	else if null{
	}
	else{
	}
}
action def{
	action ordered while null action{
		first MyElement;
		succession ordered first MyFeature.MyFeature if null then MyFeature;
	}
	until null;
}
action def{
	for ordered in null{
	}
}
action def{
	decide ordered;
}
action def{
	join ordered;
}
action def{
	fork ordered;
}
filter"Sample string";
filter MyElement;
filter MyElement.metadata;
filter MyFeature.MyFeature(MyFeature=null,MyFeature=null,MyFeature=null);
filter new MyFeature.MyFeature();
filter;
;
filter null;
filter null.MyFeature.MyFeature;
enum def;
state def;
view def;
view def{
	ordered;
}
state def{
	then action ordered;
}
state def{
	do assign MyFeature.MyFeature:=null;
}
