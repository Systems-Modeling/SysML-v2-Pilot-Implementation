public abstract individual action def{
	public in derived abstract constant ref individual snapshot action[true..true]ordered nonunique loop action[true..true]ordered nonunique{
		public package;
	}
}
