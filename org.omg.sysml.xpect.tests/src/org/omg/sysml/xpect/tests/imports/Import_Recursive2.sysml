package P {
    part def X;
    package Q {
      part def Y;
      package R {
        part def Z;
      }
    }
    package S {
      part def S1;
      package T {
        part def T1;
        package U {
        	part def U1;
        }
      }
    }
    
  }
