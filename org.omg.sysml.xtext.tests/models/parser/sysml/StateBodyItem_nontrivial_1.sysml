public abstract individual state def{
	then[true..true]public in derived abstract constant ref individual snapshot action[true..true]ordered nonunique=null;
	public transition accept at null via null if null do action[true..true]ordered nonunique=null{
		public package;
	}
	then[true..true]MyFeature;
	public transition accept at null via null if null do action[true..true]ordered nonunique=null{
		public package;
	}
	then[true..true]MyFeature;
}
