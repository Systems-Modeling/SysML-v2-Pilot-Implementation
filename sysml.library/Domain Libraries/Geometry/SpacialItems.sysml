/**
 * This package models physical items that have a spatial extent and act as a spatial frame of reference
 * for obtaining position and displacement vectors of points within them.
 */
package SpatialItems {
	private import Objects::Point;
	private import SpatialFrames::SpatialFrame;
	private import Shapes::Shape;
	private import CSGShapes::CsgSolid;
	private import CSGShapes::CsgUnion;
	private import ShapeCalculations::ReifyShape;
	private import SequenceFunctions::includes;
	private import Quantities::VectorQuantityValue;
	private import UnitsAndScales::VectorMeasurementReference;
	private import Time::Clock;
	private import Time::TimeInstantValue;
	private import ISQ::Cartesian3dSpatialCoordinateSystem;
	private import ControlFunctions::forAll;
	private import ControlFunctions::reduce;
	
	/**
	 * A SpatialItem is an Item with a three dimensional spatial extent that also acts as a SpacialFrame of reference.
	 */
	item def SpatialItem :> SpatialFrame {
		/**
		 * A local Clock to be used as the corresponding time reference within this SpatialItem
		 * and any componentItems. By default this is the global defaultClock.
		 */
		item localClock : Clock[1] default Time::defaultClock;
		
		/**
		 * The VectorMeasurementReference to be used as the measurement reference for position and displacement
		 * vector values relative to this SpatialItem.
		 */
		attribute coordinateSystem : VectorMeasurementReference[1] default Cartesian3dSpatialCoordinateSystem() {
			attribute :>> dimensions = 3;
		}
		
		/**
		 * A Shape that specifies the envelope that contains this SpatialItem.
		 */
		attribute boundingShape : Shape[0..1];
		
		/**
		 * A SpatialItem must be an enclosed space-time Occurrence of the reification of its bounding shape.
		 */
		assert constraint boundingShapeConstraint {
			boundingShape != null implies
				ReifyShape(boundingShape).subSpaceTimeOccurrences->includes(self)
		}
	}
	
	/**
	 * A CompoundSpatialItem is a SpatialItem that is a union of a collection of component SpatialItems.
	 */
	item def CompoundSpatialItem :> SpatialItem {
		
		/**
		 * By default the boundingShape of a CompoundSpatialItem is the union of the
		 * boundingShapes of its componentItems, if all the componentItems have
		 * boundingShapes that are CsgSolids.
		 */
		attribute :>> boundingShape default
			if componentItems->forAll{in i : SpatialItem; 
				i.boundingShape != null and i.boundingShape istype CsgSolid
			}? CsgUnion(componentItems.boundingShape as CsgSolid)
			else null;
		
		/**
		 * The composite SpatialItems that together make up this CompoundSpatialItem.
		 */
		item componentItems : SpatialItem[1..*] ordered :> subitems {
			item nestedLocalClock :>> localClock default localClock;
			attribute nestedBasisDirections : VectorQuantityValue[3];
			attribute nestedOrigin : VectorQuantityValue[0..1];
			attribute nestedCoordinateSystem :>> coordinateSystem {
				attribute :>> placement[1] {
				 	attribute :>> source = coordinateSystem;
				 	attribute :>> target = nestedCoordinateSystem;
				 	attribute :>> basisDirections = nestedBasisDirections;
				 	attribute :>> origin = nestedOrigin;
				}
			}
		}
		
		/**
		 * A CompoundSpatialItem is a spatial union of its componentItems.
		 */
		attribute componentUnion[1] :> unionsOf {
			item :>> elements = componentItems;
		}
	}
	
	/**
	 * The PositionOf a Point relative to a SpatialItem, at a specific TimeInstantValue relative to a given Clock,
	 * is a positionVector that is a VectorQuantityValue in the coordinateSystem of the SpatialItem.
	 * The default Clock is the localClock of the SpatialItem.
	 */
	calc def PositionOf :> SpatialFrames::PositionOf {
		in point : Point[1];
		in timeInstant : TimeInstantValue[1];
		in enclosingItem :>> 'frame' : SpatialItem[1];
		in clock : Clock[1] default enclosingItem.localClock;
		return positionVector : VectorQuantityValue[1] {
			attribute :>> mRef = enclosingItem.coordinateSystem;
		}
	}

	/**
	 * The CurrentPositionOf a Point relative to a SpatialItem and a Clock is the PositionOf
	 * the Point relative to the SpatialItem at the currentTime of the Clock.
	 */
	calc def CurrentPositionOf :> SpatialFrames::CurrentPositionOf {
		in point : Point[1];
		in enclosingItem :>> 'frame' : SpatialItem[1];
		in clock : Clock[1] default enclosingItem.localClock;
		return positionVector : VectorQuantityValue[1] {
			attribute :>> mRef = enclosingItem.coordinateSystem;
		}
	}

	/**
	 * The DisplacementOf two Points relative to a SpatialItem, at a specific TimeInstantValue relative to a
	 * given Clock, is the displacementVector computed as the difference between the PositionOf the 
	 * first Point and PositionOf the second Point, relative to that SpatialItem, at that timeInstant.
	 */
	calc def DisplacementOf :> SpatialFrames::DisplacementOf {
		in point1 : Point[1];
		in point2 : Point[1];
		in timeInstant : TimeInstantValue[1];
		in enclosingItem :>> 'frame' : SpatialItem[1];
		in clock : Clock[1] default enclosingItem.localClock;
		return positionVector : VectorQuantityValue[1] {
			attribute :>> mRef = enclosingItem.coordinateSystem;
		}
	}

	/**
	 * The CurrentDisplacementOf two Points relative to a SpatialItem and a Clock is the DisplacementOf
	 * the Points relative to the SpacialItem, at the currentTime of the Clock.
	 */
	calc def CurrentDisplacementOf :> SpatialFrames::CurrentDisplacementOf {
		in point1 : Point[1];
		in point2 : Point[1];
		in enclosingItem :>> 'frame' : SpatialItem[1];
		in clock : Clock[1] default enclosingItem.localClock;
		return positionVector : VectorQuantityValue[1] {
			attribute :>> mRef = enclosingItem.coordinateSystem;
		}
	}

}
