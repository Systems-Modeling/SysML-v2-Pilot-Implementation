public abstract individual action def{
	public in derived abstract constant ref individual snapshot action[true..true]ordered nonunique while null action[true..true]ordered nonunique{
		public package;
	}
	until null;
}
