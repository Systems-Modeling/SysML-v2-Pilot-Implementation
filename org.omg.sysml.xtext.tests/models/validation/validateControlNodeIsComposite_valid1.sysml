// Constraint: validateControlNodeIsComposite (context: ControlNode)
// A ControlNode must be composite.
// isComposite
package validateControlNodeIsComposite_valid1 {
	action def A {
		merge m;
	}
}
