public const end in derived abstract composite var all[true..true]ordered nonunique binding all[true..true]ordered nonunique{
	public member const end in derived abstract composite var all[true..true]ordered nonunique feature all[true..true]ordered nonunique=null;
}
