package 'Merge Example' {
	part def Scene;
	part def Image;
	part def Picture;
	
	action def Focus(in item scene : Scene, out item image : Image);
	action def Shoot(in item image : Image, out item picture : Picture);
	action def Display(in item picture : Picture);
	action def TakePicture;
	
	action takePicture : TakePicture {
		first start;
		
		then merge continue;
			
		then action trigger {
			out item scene : Scene;
		}
		
		flow from trigger.scene to focus.scene;
		
		then action focus : Focus {
			in item scene;
			out item image;
		}
		
		flow from focus.image to shoot.image;
		
		then action shoot : Shoot {
			in item image ;
			out item picture;
		}
		
		flow from shoot.picture to display.picture;
		
		then action display : Display {
			in item picture;
		}
		
		then continue;	
	}
}
