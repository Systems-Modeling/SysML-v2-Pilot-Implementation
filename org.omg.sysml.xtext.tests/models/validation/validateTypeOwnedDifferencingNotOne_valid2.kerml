// Constraint: validateTypeOwnedDifferencingNotOne (context: Type)
// A Type must not have exactly one ownedDifferencing.
// ownedDifferencing->size() <> 1
package validateTypeOwnedDifferencingNotOne_valid2 {
	classifier T;
}
