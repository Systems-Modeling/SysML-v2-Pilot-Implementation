public const end in derived abstract composite var all[true..true]ordered nonunique bool all[true..true]ordered nonunique{
	public return const end in derived abstract composite var all[true..true]ordered nonunique feature all[true..true]ordered nonunique=null;
}
