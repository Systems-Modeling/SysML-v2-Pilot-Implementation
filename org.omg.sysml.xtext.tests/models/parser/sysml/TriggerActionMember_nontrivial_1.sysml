public abstract individual state def{
	public in derived abstract constant ref individual snapshot action[true..true]ordered nonunique=null;
	public transition accept at null via null then[true..true]MyFeature;
}
