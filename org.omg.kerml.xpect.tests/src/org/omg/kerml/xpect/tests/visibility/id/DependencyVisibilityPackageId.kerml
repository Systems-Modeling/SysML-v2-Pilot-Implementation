package VP {
			
	package VP1 {	
		public class id 'c_Public_Id' c_Public {
			private class c_private{}
			public class c_public{}
			protected class c_protected{}
		}
	}
	
	package VP2 {
			
		public class id 'A_Id' AAAAA;
	}
}
