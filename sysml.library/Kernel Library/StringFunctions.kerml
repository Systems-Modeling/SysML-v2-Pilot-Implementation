package StringFunctions {
	import ScalarValues::*;
	
	function '+'(x: String, y:String): String specializes ScalarFunctions::'+';
	
	function Size(x: String): Natural;
	function Substring(x: String, lower: Integer, upper: Integer): String;
	
	function '<'(x: String, y: String): Boolean specializes ScalarFunctions::'<';
	function '>'(x: String, y: String): Boolean specializes ScalarFunctions::'>';
	function '<='(x: String, y: String): Boolean specializes ScalarFunctions::'<=';
	function '>='(x: String, y: String): Boolean specializes ScalarFunctions::'>=';

	function '='(x: String, y: String): Boolean specializes BaseFunctions::'==';
	function '!='(x: String, y: String): Boolean specializes BaseFunctions::'!=';
	
	function ToString(x: String): String specializes BaseFunctions::ToString;	
}
