public abstract individual action def{
	then[true..true]public in derived abstract constant ref individual snapshot action[true..true]ordered nonunique send null via null to null;
	public[true..true]then[true..true]MyFeature;
	public[true..true]then[true..true]MyFeature;
}
