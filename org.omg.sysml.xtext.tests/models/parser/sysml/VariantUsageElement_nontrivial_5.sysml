public abstract individual interface def{
	public variant end in derived abstract constant ref[true..true]ordered nonunique succession[true..true]ordered nonunique first[true..true]MyFeature then[true..true]MyFeature;
}
