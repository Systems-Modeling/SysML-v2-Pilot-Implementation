package '1d-Parts Tree with Reference' {
	
	package Definitions {
		block Vehicle;
		block Trailer;
		block TrailerHitch;
		block HitchBall;
		block TrailerCoupler;
	}
	
	package Usages {
		import Definitions::*;
		
		part vehicle_trailer_system {
			
			part vehicle1_c1: Vehicle {
				/**
				 * 'vehicle1_c1'::'hitchBall' is a reference property that
				 * references a hitch ball that is not part of this vehicle. 
				 * If 'vehicle1_c1' is removed or destroyed, this does not
				 * effect the hitchBall referenced here.
				 */
				ref hitchBall : HitchBall;
			}
			
			/**
			 * This is a binding connector between the 'hitchBall' in 'vehicle1_c1'
			 * and the 'hitchBall' in 'trailerHitch'.
			 */			
			bind vehicle1_c1::hitchBall = trailerHitch::hitchBall;
			
			part trailerHitch: TrailerHitch {				
				part hitchBall: HitchBall;
				part trailerCoupler: TrailerCoupler;
			}
			
			part trailer1: Trailer {
				/**
				 * This is a shorthand for a binding connector between the
				 * 'trailerCoupler' here and the 'trailerCoupler' in 'trailerHitch'.
				 * The binding connector is now contained within the 'trailer1'
				 * part, though, rather than being at the system level. 
				 */
				ref trailerCoupler : TrailerCoupler = trailerHitch::trailerCoupler;
			}
		}
	}
}
