public abstract individual interface def{
	public variant end in derived abstract constant ref[true..true]ordered nonunique binding[true..true]ordered nonunique bind[true..true]MyFeature=[true..true]MyFeature;
}
