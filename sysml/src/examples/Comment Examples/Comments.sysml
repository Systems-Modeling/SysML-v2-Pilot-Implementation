/** Documentation Comment */
package Comments {
	comment doc_about_doc /** Comment about Comment */
	comment doc /* Named Comment */	
	comment doc_doc about doc /* Other Comment about Comment */
	
	comment /** Documention Comment on Block */
	part def C {
		comment /* Comment in Block */
		comment about Comments /* Comment about Package */
	}
}
