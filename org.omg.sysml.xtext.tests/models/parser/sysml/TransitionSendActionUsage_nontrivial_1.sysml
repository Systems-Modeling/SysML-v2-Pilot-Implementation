public abstract individual state def{
	public in derived abstract constant ref individual snapshot action[true..true]ordered nonunique=null;
	public transition do action[true..true]ordered nonunique send null via null to null{
		public package;
		public package;
	}
	then[true..true]MyFeature;
}
