package '3e-Function-based Behavior-item' {
	import Definitions::*;
	
	package Definitions {
		
		item def VehicleAssembly;
		item def AssembledVehicle :> VehicleAssembly;
		
		part def Vehicle :> AssembledVehicle;		
		part def Transmission;
		part def Engine;		
		
	}
	
	package Usages {
		
		part AssemblyLine {
		
			perform action 'assemble vehicle' {
				
				action 'assemble transmission into vehicle' {
					/**
					 * Note: The "flows" of an action should be considered to be its parameters.
					 */
					item in 'vehicle assy without transmission or engine' : VehicleAssembly;
					/** Note: A part can be treated as an item. */
					item in transmission : Transmission;
					
					item out 'vehicle assy without engine' : VehicleAssembly = 'vehicle assy without transmission or engine' {
						/** Note: An item can become a part of something else. */
						part transmission : Transmission = 'assemble transmission into vehicle'::transmission;
					}
				}
				
				flow 'assemble transmission into vehicle'::'vehicle assy without engine' 
				    to 'assemble engine into vehicle'::'vehicle assy without engine';
				
				action 'assemble engine into vehicle' {
					item in 'vehicle assy without engine' : VehicleAssembly {
						part transmission : Transmission;
					}
					item in engine : Engine;
					
					item out assembledVehicle : AssembledVehicle = 'vehicle assy without engine' {
						part engine : Engine = 'assemble engine into vehicle'::engine;
					}
				}
			}
			
			bind 'assemble vehicle'::'assemble engine into vehicle'::assembledVehicle = vehicle;
			
			/**
			 * Note: An item in one context can become a part in an other.
			 */
			part vehicle : Vehicle {
				part transmission: Transmission;
				part engine: Engine;
				
				perform action providePower;
			}
			
		}
	}
}
