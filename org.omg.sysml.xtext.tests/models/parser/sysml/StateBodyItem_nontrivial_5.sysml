public abstract individual state def{
	public transition[true..true]ordered nonunique first MyFeature.MyFeature accept at null via null if null do action[true..true]ordered nonunique=null{
		public package;
	}
	then[true..true]MyFeature;
}
