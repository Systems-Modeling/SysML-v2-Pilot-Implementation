package P {
    class X;
    package Q {
      class Y;
      package R {
        class Z;
      }
    }
    package S {
      class S1;
      package T {
        class T1;
        package U {
        	class U1;
        }
      }
    }
    
  }
