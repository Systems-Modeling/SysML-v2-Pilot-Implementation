comment<BasicName>BasicName about MyElement,MyElement,MyElement locale"Sample string"/* Sample comment */public alias<'Unrestricted Name'>BasicName for MyElement{
	#MyType#MyType dependency from MyElement,MyElement,MyElement to MyElement,MyElement,MyElement{
	}
	doc locale"Sample string"/* Sample comment */
}
inverting inverse MyFeature of MyFeature;
dependency from MyElement to MyElement;
comment about MyElement/* Sample comment */@:MyType about MyElement;
connector all MyType to MyType;
connector BasicName from MyType to MyType;
binding of MyType=MyType;
succession first MyType then MyType;
conjugate MyType~MyType;
disjoint MyType from MyType;
inverse MyFeature of MyFeature;
bool default=MyElement@@MyType;
public import MyMembership[MyElement meta MyType];
portion var feature:>>MyType,MyType,MyType[true]ordered nonunique;
connector from MyType to MyType;
binding~MyType of MyType=MyType;
succession ordered first MyType then MyType;
dependency MyElement to MyElement;
public import MyMembership[null->MyFeature.MyFeature MyType];
metadata MyType{
	feature MyType nonunique ordered:MyType:MyType=null;
}
#MyType@MyType{
	redefines MyType;
}
public import MyMembership[as MyType];
end ordered=null;
connector ordered(MyType,MyType);
public import MyMembership[null->MyFeature.MyFeature(null,null,null)];
comment/* Sample comment */ordered;
inv true;
bool default null;
inv ordered=null;
connector;
subclassifier MyClassifier:>MyClassifier;
featuring MyFeature by MyType;
flow ordered=null;
flow MyFeature to MyFeature;
type~MyType;
standard library package{
}
typing MyFeature:MyType;
language"Sample string"/* Sample comment */multiplicity[true...55];
multiplicity[true..55E55];
bool:=null;
connector all from MyType to MyType;
connector MyType to MyType;
subtype MyType:>MyType;
subset MyType:>MyType;
redefinition MyType:>>MyType;
public import MyNamespace::*;
doc/* Sample comment */bool=null;
bool BasicName disjoint from MyType;
bool BasicName featured by MyType;
step;
expr;
bool;
flow of[true]MyType;
flow of:MyType:MyType:MyType:MyType=null;
flow of ordered:MyType:MyType;
public import MyNamespace::*[null];
/* Sample comment */bool BasicName unions MyType;
bool BasicName intersects MyType;
bool BasicName differences MyType;
bool BasicName chains MyFeature.MyFeature;
binding MyType=MyType;
flow of:MyType nonunique;
flow of MyType;
type[true]:>MyType;
function:>MyClassifier;
public import MyMembership[null#(null)][null];
public import MyNamespace::*::**[null];
bool[true];
binding;
binding ordered;
succession;
succession ordered;
flow from MyFeature to MyFeature;
namespace{
}
package;
public import MyMembership[null->MyFeature.MyFeature(null)];
public import MyMembership[null->MyFeature.MyFeature(MyFeature=null)];
bool ordered:MyType;
bool ordered:>MyType;
bool ordered:>>MyType;
bool ordered{
}
bool~MyType;
bool BasicName inverse of MyFeature;
bool ordered=null;
#MyType#MyType namespace{
	namespace;
	namespace;
}
rep language"Sample string"/* Sample comment */#MyType#MyType@typed by MyType about MyElement,MyElement,MyElement{
	namespace;
	:>>MyFeature.MyFeature.MyFeature{
	}
}
#MyType@MyType{
	alias for MyElement;
}
#MyType@MyType{
	public import MyMembership;
}
bool ordered crosses MyType;
multiplicity[true..55];
multiplicity[true..55.55e+55];
multiplicity[true..*];
multiplicity[true..false];
multiplicity[true..55e-55];
public import MyMembership[null or null];
public import MyMembership[null and null];
public import MyMembership[null implies null];
public import MyMembership[null&null];
public import MyMembership[null xor null];
public import MyMembership[null..null];
public import MyMembership[null==null];
public import MyMembership[null!=null];
public import MyMembership[null===null];
public import MyMembership[null!==null];
public import MyMembership[null<null];
public import MyMembership[null>null];
public import MyMembership[null<=null];
public import MyMembership[null>=null];
public import MyMembership[null+null];
public import MyMembership[null-null];
public import MyMembership[null*null];
public import MyMembership[null/null];
public import MyMembership[null%null];
public import MyMembership[null^null];
public import MyMembership[null**null];
public import MyMembership[-null];
public import MyMembership[~null];
public import MyMembership[not null];
public import MyMembership[hastype MyType];
public import MyMembership[@MyType];
public import MyMembership[(null)];
public import MyMembership[null.?{
}
];
public import MyMembership[null.{
}
];
public import MyMembership[null[all MyType,].MyElement->MyElement{
	return const end in derived abstract composite const all<BasicName>BasicName:MyType,MyType,MyType references MyType:>MyType,MyType,MyType=>MyType intersects MyType,MyFeature.MyFeature,MyType chains MyFeature#MyType#MyType#MyType{
		namespace;
		member end step<BasicName>conjugates MyFeature.MyFeature default:=+null{
		}
	}
	return feature;
	null|null
}
];
public import MyMembership[()];
public import MyMembership[(null,null)];
binding{
	expr ordered=null;
}
connector ordered=null;
binding all MyType=MyType;
succession all MyType then MyType;
flow all MyFeature to MyFeature;
succession flow of MyType[true]from MyType.MyFeature to MyFeature;
out ordered;
inout ordered;
bool BasicName inverse of MyFeature.MyFeature;
bool BasicName featured by MyType,MyType,MyType;
connector([MyElement..true]BasicName::>MyType,MyType,MyType,MyType);
alias for MyElement{
	inv false{
		alias for MyElement;
		private import all MyMembership::**;
	}
}
type all[true]specializes MyType,MyType,MyType differences MyType,MyFeature.MyFeature,MyType disjoint from MyType;
classifier~MyType;
datatype;
class;
struct;
metaclass;
assoc;
abstract#MyType#MyType assoc struct all[true]:>MyClassifier,MyClassifier,MyClassifier disjoint from MyFeature.MyFeature,MyType,MyType unions MyType,MyFeature.MyFeature,MyType;
interaction;
behavior;
function;
predicate;
multiplicity:>MyType;
#MyType#MyType package{
	protected import MyNamespace::*::**;
	namespace;
}
standard library#MyType#MyType package{
	filter if null?null??null else null istype MyType;
	filter null;
}
specialization subtype MyFeature.MyFeature:>MyType;
conjugation conjugate MyFeature.MyFeature~MyFeature.MyFeature;
specialization subclassifier MyClassifier:>MyClassifier;
disjoining disjoint MyFeature.MyFeature from MyFeature.MyFeature;
inverting inverse MyFeature.MyFeature of MyFeature.MyFeature;
specialization typing MyFeature typed by MyType;
specialization subset MyType subsets MyType;
specialization redefinition MyType redefines MyType;
featuring of MyFeature by MyType;
#MyType namespace;
multiplicity[true];
public import MyMembership["Sample string"];
public import MyMembership[MyElement];
public import MyMembership[MyElement.metadata];
public import MyMembership[MyFeature.MyFeature(MyFeature=null,MyFeature=null,MyFeature=null)];
public import MyMembership[new MyFeature.MyFeature()];
public import MyMembership[{
}
];
public import MyMembership[null];
public import MyMembership[null.MyFeature.MyFeature];
