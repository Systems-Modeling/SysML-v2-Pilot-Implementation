package P {
    class X {
    	class X1;
    }
    package Q {
      class Y;
      package R {
        class Z;
      }
    }
    package S {
      class S1 specializes X;
      package T {
        class T1;
        package U {
        	class U1;
        }
      }
    }
    
  }
