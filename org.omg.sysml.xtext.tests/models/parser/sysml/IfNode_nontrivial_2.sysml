public abstract individual action def{
	public in derived abstract constant ref individual snapshot action[true..true]ordered nonunique if null action[true..true]ordered nonunique{
		public package;
	}
	else in derived abstract constant ref individual snapshot action[true..true]ordered nonunique if null action[true..true]ordered nonunique{
		public package;
	}
	else action[true..true]ordered nonunique{
		public package;
	}
}
