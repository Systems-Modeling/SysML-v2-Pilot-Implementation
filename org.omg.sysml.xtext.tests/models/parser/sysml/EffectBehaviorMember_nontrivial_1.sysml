public abstract individual state def{
	public in derived abstract constant ref individual snapshot action[true..true]ordered nonunique=null;
	public transition do action[true..true]ordered nonunique=null{
		public package;
	}
	then[true..true]MyFeature;
}
