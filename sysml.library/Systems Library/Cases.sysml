/**
 * This package defines the base types for cases and related behavioral elements 
 * in the SysML language.
 */
package Cases {
	private import Base::Anything;
	private import Requirements::RequirementCheck;
	private import Calculations::Calculation;
	private import Calculations::calculations;
	
	/**
	 * Case is the most general class of performances of CaseDefinitions. 
	 * Case is the base class of all CaseDefinitions.
	 */
	abstract case def Case :> Calculation () result[0..*] {
		ref case :>> self : Case;
		
		/**
		 * The subject that was investigated by this Case.
		 */
		subject subj : Anything[1];
		
		/**
		 * A check of whether the objective RequirementUsage was satisfied for this Case.
		 */
		objective obj : RequirementCheck[1] {
			subject = Case::result;
		}
		
		/**
		 * Other Cases carried out as part of the performance of this Case.
		 */
		abstract ref case subcases : Case[0..*] :> cases, subcalculations;
	
	}
	
	/**
	 * cases is the base Feature of all CaseUsages.
	 */
	abstract case cases : Case[0..*] :> calculations;
}
